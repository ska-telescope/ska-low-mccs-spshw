SEVEN-PRODUCT-MIB DEFINITIONS ::= BEGIN

-- During development all unused/not implemented objects are commented out
-- to avoid later changes

-- IMPORTS: Include definitions from other mibs here
IMPORTS
        OBJECT-TYPE, Integer32, Unsigned32,
        MODULE-IDENTITY, NOTIFICATION-TYPE, enterprises      FROM SNMPv2-SMI
        DisplayString, DateAndTime                              FROM SNMPv2-TC
        NOTIFICATION-GROUP                                      FROM SNMPv2-CONF;

    

-- A brief description and update information about this mib.
-- (I follow the CamelCase to be sure I don't mistype. Who knows the rules...

sevensolsProducts MODULE-IDENTITY
    LAST-UPDATED "201701170000Z"
    ORGANIZATION "Seven Solutions"
    CONTACT-INFO "postal:   Calle Periodista Rafael Gomez Montero, 2. CETIC-UGR 13, 18014. Granada - SPAIN
                  email:    info@sevensols.com
                 "
    DESCRIPTION  "Seven Solutions Product MIB
                 "
    REVISION     "201701170000Z"
    DESCRIPTION
        "First revision."
    ::= { sevensols 1 }

sevensols OBJECT IDENTIFIER ::= { enterprises 49029 }



-- Define typical mib nodes
wrzTPFamily             OBJECT IDENTIFIER ::= { sevensolsProducts 10 }
wrzTPFamilyNotifications    OBJECT IDENTIFIER ::= { wrzTPFamily 100}
wrzNotificationsPrefix      OBJECT IDENTIFIER ::= { wrzTPFamilyNotifications 2 }
wrzNotificationsObjects     OBJECT IDENTIFIER ::= { wrzTPFamilyNotifications 3 }

-- wrzGeneralStatus 
-- OID: (.1.3.6.1.4.1.49029.1.10.1)

wrzGeneralStatus   OBJECT-TYPE
    SYNTAX    INTEGER {
                        ok(1),
                        modNotShMem(200),
                        modDown(201),
                        modUnknownStatus(202),
                        modParamsNotSync(203),
                        modParamsCritical(204),
                        modParamsWarning(205),                                    
    }
    MAX-ACCESS  read-only
    STATUS    current
    DESCRIPTION
        "ok (1)                 - All modules is up and all parameters of the modules are ok.
         modNotShMem(200)       - At least one module share memory file is not found and there aren't modules down.
         modDown(201)           - At least one module is not running
         modUnknownStatus(202)  - At least one module is in unknown status and there aren't modules down or without share mem.
         modParamsNotSync(203)  - At least one parameter in a module is out of sync and there aren't modules in previous states.
         modParamsCritical(204) - At least one parameter in a module is critical and there aren't modules in previous states.
         modParamsWarning(205)  - At least one parameter in a module is in warning range and there aren't modules in previous states.
         "
    ::= { wrzTPFamily 1 }


-- wrzModuleTable 
-- OID: (.1.3.6.1.4.1.49029.1.10.2)

wrzModuleTable OBJECT-TYPE
    SYNTAX    SEQUENCE OF WrzModulesEntry
    MAX-ACCESS  not-accessible
    STATUS    current
    DESCRIPTION
    "This table has a list of all modules running in the device.
    With this table you can review the general status of the switch.
    If one of the parameter in the module has a warning or error you
    can review it watching column wrzModuleStatus.
    The rows of this table are preloaded. One row per module."
    ::= { wrzTPFamily 2 }

wrzModulesEntry OBJECT-TYPE
    SYNTAX    WrzModulesEntry
    MAX-ACCESS  not-accessible
    STATUS    current
    DESCRIPTION
    "A row describing a given working group"
    INDEX   { wrzModuleIndex }
    ::= {wrzModuleTable 1 }

WrzModulesEntry ::= SEQUENCE {
    wrzModuleIndex          Unsigned32,
    wrzModuleName               DisplayString,
    wrzModuleStatus         INTEGER,
    wrzModuleTotalNotSync       INTEGER,
    wrzModuleTotalWarnings  INTEGER,
    wrzModuleTotalCriticals INTEGER,
    wrzModuleLastBoot           DisplayString,
    wrzModuleLastSync           DisplayString
}

wrzModuleIndex      OBJECT-TYPE
    SYNTAX    Unsigned32
    MAX-ACCESS  not-accessible
    STATUS    current
    DESCRIPTION
    "The index of the module"
    ::= { wrzModulesEntry 1 }

wrzModuleName       OBJECT-TYPE
    SYNTAX    DisplayString
    MAX-ACCESS  read-only
    STATUS    current
    DESCRIPTION
    "The name of the module"
    ::= { wrzModulesEntry 2 }
    
wrzModuleStatus OBJECT-TYPE
    SYNTAX    INTEGER {
                        ok(1),
                        modNotShMem(200),
                        modDown(201),
                        modUnknownStatus(202),
                        modParamsNotSync(203),
                        modParamsCritical(204),
                        modParamsWarning(205),                                    
    }
    MAX-ACCESS  read-only
    STATUS    current
    DESCRIPTION
    "The status of the module.
        ok(1)                   - Module is up and all parameter of the module are ok.
        modNotShMem(200)        - Cannot find share memory file.
        modDown(201)            - Module is not running.
        modUnknownStatus(202)   - Bug state, if not matching with other conditions.
        modParamsNotSync(203)   - At least one parameter is out of sync.
        modParamsCritical(204)  - At least one parameter of the module is in critical. range and there aren't parameters out of sync.
        modParamsWarning(205)   - At least one parameter of the module is in warning range, and there aren't parameters out of sync or in critical range.
    "
     ::= { wrzModulesEntry 3 }

wrzModuleTotalNotSync   OBJECT-TYPE
    SYNTAX              INTEGER
    MAX-ACCESS              read-only
    STATUS              current
    DESCRIPTION
    "Time of last boot"
    ::= { wrzModulesEntry 4 }
    
wrzModuleTotalWarnings  OBJECT-TYPE
    SYNTAX              INTEGER
    MAX-ACCESS              read-only
    STATUS              current
    DESCRIPTION
    "Time of last boot"
    ::= { wrzModulesEntry 5 }
    
wrzModuleTotalCriticals OBJECT-TYPE
    SYNTAX              INTEGER
    MAX-ACCESS              read-only
    STATUS              current
    DESCRIPTION
    "Time of last boot"
    ::= { wrzModulesEntry 6 }

wrzModuleLastBoot   OBJECT-TYPE
    SYNTAX      DisplayString
    MAX-ACCESS      read-only
    STATUS      current
    DESCRIPTION
    "Time of last boot"
    ::= { wrzModulesEntry 7 }
    
wrzModuleLastSync   OBJECT-TYPE
    SYNTAX      DisplayString
    MAX-ACCESS      read-only
    STATUS      current
    DESCRIPTION
    "Time of last boot"
    ::= { wrzModulesEntry 8 }   


-- wrzModuleParamTable 
-- OID: (.1.3.6.1.4.1.49029.1.10.3)

wrzParamTable OBJECT-TYPE
    SYNTAX    SEQUENCE OF WrzParamsEntry
    MAX-ACCESS  not-accessible
    STATUS    current
    DESCRIPTION
    "This table has a list of parameters running in the switch.
    This table is related with wrzModuleTable.
    Each parameter has an index related to its parent module.
    The rows of this table are preloaded.
    The values of the parameters can be setting throw SNMP if 
    this parameter allows write operations.
    Each perameter is identified by its module, prefix and parameter index.
    This table preload the relationship between indexes and prefixName and paramName.
    One a parameter is assigned to an index in this table 
    it belongs to this parameter forever.
    "
    ::= { wrzTPFamily 3 }

wrzParamsEntry OBJECT-TYPE
    SYNTAX    WrzParamsEntry
    MAX-ACCESS  not-accessible
    STATUS    current
    DESCRIPTION
    "A row describing a given working group"
    INDEX   { wrzModuleIndex, wrzParamPrefixIndex, wrzParamIndex }
    ::= {wrzParamTable 1 }

WrzParamsEntry ::= SEQUENCE {
    wrzParamPrefixIndex Unsigned32,
    wrzParamIndex           Unsigned32,
    wrzParamModuleName  DisplayString,
    wrzParamPrefixName  DisplayString,
    wrzParamName            DisplayString,
    wrzParamType            DisplayString,
    wrzParamVal         DisplayString,
    wrzParamUnit            DisplayString,
    wrzParamStatus      INTEGER,
    wrzParamLastSync        DisplayString
}   

wrzParamPrefixIndex         OBJECT-TYPE
    SYNTAX    Unsigned32
    MAX-ACCESS  not-accessible
    STATUS    current
    DESCRIPTION
    "The index of Prefix belongs to a Module."
    ::= { wrzParamsEntry 1 }

wrzParamIndex       OBJECT-TYPE
    SYNTAX    Unsigned32
    MAX-ACCESS  not-accessible
    STATUS    current
    DESCRIPTION
    "The index of Parameter belongs to a Prefix."
    ::= { wrzParamsEntry 2 }

wrzParamModuleName      OBJECT-TYPE
    SYNTAX    DisplayString
    MAX-ACCESS  read-only
    STATUS    current
    DESCRIPTION
    "The name of the Module containing the Parameter."
    ::= { wrzParamsEntry 3 }

wrzParamPrefixName      OBJECT-TYPE
    SYNTAX    DisplayString
    MAX-ACCESS  read-only
    STATUS    current
    DESCRIPTION
    "The name of the Prefix containing the Parameter."
    ::= { wrzParamsEntry 4 }

wrzParamName    OBJECT-TYPE
    SYNTAX    DisplayString
    MAX-ACCESS  read-only
    STATUS    current
    DESCRIPTION
    "The name of the Parameter."
    ::= { wrzParamsEntry 5 }
            
wrzParamType    OBJECT-TYPE
    SYNTAX    DisplayString
    MAX-ACCESS  read-only
    STATUS    current
    DESCRIPTION
    "The type of data stored in the Parameter"
    ::= { wrzParamsEntry 6 }
    
wrzParamVal     OBJECT-TYPE
    SYNTAX    DisplayString
    MAX-ACCESS  read-write
    STATUS    current
    DESCRIPTION
    "The name value of the Parameter represented as String. Not all the parameters
    are writable. See wrzParamXAccess."
    ::= { wrzParamsEntry 7 }
    
wrzParamUnit    OBJECT-TYPE
    SYNTAX    DisplayString
    MAX-ACCESS  read-only
    STATUS    current
    DESCRIPTION
    "The unit of the parameter."
    ::= { wrzParamsEntry 8 }
    
wrzParamStatus  OBJECT-TYPE
    SYNTAX     INTEGER {
                        ok(1),
                        modNotShMem(200),
                        modDown(201),
                        modUnknownStatus(202),
                        paramNotFound(301),
                        paramUnknown(302),
                        paramNotSync(303) ,
                        paramCritical(304),
                        paramWarning(305)
    }
    MAX-ACCESS  read-only
    STATUS    current
    DESCRIPTION
    "The status of the module.
        ok(1)                   - Parameter is ok.
        modNotShMem(200)        - Cannot find share memory file.
        modDown(201)            - Module is not running.
        modUnknownStatus(202)   - Bug state, if not matching with other conditions.
        paramNotFound(301)      - Parameter is not found in the module. This error happens if an parameter is load for SNMP but module is not supporting this parameter now.
        paramUnknown(302)       - Bug state, if not matching with other conditions.
        paramNotSync(303)       - Parameter is not sync with its resource.
        paramCritical(304)      - Parameter is in critical range and sync.
        paramWarning(305)       - Parameter is in warning range and sync, and not in critical range.
        "
    ::= { wrzParamsEntry 9 }
    
wrzParamLastSync    OBJECT-TYPE
    SYNTAX    DisplayString
    MAX-ACCESS  read-only
    STATUS    current
    DESCRIPTION
    "The name of the IETF Working Group this table describes."
    ::= { wrzParamsEntry 10 }

-- wrzParamXTable 
-- OID: (.1.3.6.1.4.1.49029.1.10.4)

wrzParamXTable OBJECT-TYPE
    SYNTAX    SEQUENCE OF WrzParamsXEntry
    MAX-ACCESS  not-accessible
    STATUS    current
    DESCRIPTION
    "This table is an augmented table with extra columns describing the parameters.
     This table allows change config values, which are loaded when a module starts."
    ::= { wrzTPFamily 4 }

wrzParamsXEntry OBJECT-TYPE
    SYNTAX    WrzParamsXEntry
    MAX-ACCESS  not-accessible
    STATUS    current
    DESCRIPTION
    "A row describing a given working group"
    AUGMENTS   { wrzParamsEntry }
    ::= {wrzParamXTable 1 }

WrzParamsXEntry ::= SEQUENCE {
    wrzParamXModuleName     DisplayString,
    wrzParamXPrefixName     DisplayString,
    wrzParamXName               DisplayString,
    wrzParamXAccess         INTEGER,
    wrzParamXConfigVal      DisplayString,
    wrzParamXSetRange           DisplayString,
    wrzParamXWarningRange       DisplayString,
    wrzParamXCriticalRange  DisplayString,  
    wrzParamXDescription        DisplayString
}   

wrzParamXModuleName     OBJECT-TYPE
    SYNTAX    DisplayString
    MAX-ACCESS  read-only
    STATUS    current
    DESCRIPTION
    "The name of the Module containing the Parameter."
    ::= { wrzParamsXEntry 1 }

wrzParamXPrefixName     OBJECT-TYPE
    SYNTAX    DisplayString
    MAX-ACCESS  read-only
    STATUS    current
    DESCRIPTION
    "The name of the Prefix containing the Parameter."
    ::= { wrzParamsXEntry 2 }

wrzParamXName           OBJECT-TYPE
    SYNTAX    DisplayString
    MAX-ACCESS  read-only
    STATUS    current
    DESCRIPTION
    "The name of the Parameter."
    ::= { wrzParamsXEntry 3 }

wrzParamXAccess         OBJECT-TYPE
    SYNTAX    INTEGER {
                        R(1),
                        RW(2),
                        RL(3),
                        RWL(4)
    }
    MAX-ACCESS  read-only
    STATUS    current
    DESCRIPTION
    "The access to the parameter.
        R       (1) - The value of the parameter is read-only
        RW      (2) - The value of the parameter is read-write
        RL      (3) - The value of the parameter is read-only but it's possible to change config value
        RWL     (4) - The value of the parameter is read-write and its value is loaded from dot-config file"
      ::= { wrzParamsXEntry 4 }

wrzParamXConfigVal OBJECT-TYPE
    SYNTAX    DisplayString
    MAX-ACCESS  read-write
    STATUS    current
    DESCRIPTION
    "The config value of a parameter. This value is loading from .config file to a parameter when modules boot.
    When you change a value, you can watch the valued marked with an '*'. This means that the Config Value is
    not been saved yet to its dot-config file. To save all the values marked with '*' use wrzCommands. Review
    this parameter to understand how to save and apply.
    "
    ::= { wrzParamsXEntry 5 }

wrzParamXSetRange OBJECT-TYPE
    SYNTAX    DisplayString
    MAX-ACCESS  read-only
    STATUS    current
    DESCRIPTION
    "The range with corrects values to set."
    ::= { wrzParamsXEntry 6 }
    
wrzParamXWarningRange OBJECT-TYPE
    SYNTAX    DisplayString
    MAX-ACCESS  read-only
    STATUS    current
    DESCRIPTION
    "The range of values thar are warning values."
    ::= { wrzParamsXEntry 7 }
    
wrzParamXCriticalRange OBJECT-TYPE
    SYNTAX    DisplayString
    MAX-ACCESS  read-only
    STATUS    current
    DESCRIPTION
    "The range of values thar are critical values."
    ::= { wrzParamsXEntry 8 }   
    
wrzParamXDescription OBJECT-TYPE
    SYNTAX    DisplayString
    MAX-ACCESS  read-only
    STATUS    current
    DESCRIPTION
    "A description of the Parameter."
    ::= { wrzParamsXEntry 9 }           

-- wrzCommands 
-- OID: (.1.3.6.1.4.1.49029.1.10.99)

wrzCommands   OBJECT-TYPE
    SYNTAX    INTEGER {
                        Reboot(1),
                        PowerOff(2),
                        SaveConf(3),
                        SaveConfApply(4),
                        SaveConfReboot(5),
                        RebootSendOk(100),
                        RebootSendFail(101),
                        PowerOffSendOk(200),
                        PowerOffSendFail(201),
                        SaveConfOk(300),
                        SaveConfFail(301),
                        SaveConfWarning(302),
                        SaveConfApplyOk(400),
                        SaveConfApplyFail(401),
                        SaveConfApplyWarning(402),
                        SaveConfRebootOk(500),
                        SaveConfRebootFail(501),
                        SaveConfRebootWarning(502)
    }
    MAX-ACCESS  read-write
    STATUS    current
    DESCRIPTION
        "Run commands using SNMP. We have 5 options, for each command we received a return value:
        
        Reboot              (1) -       Reboot the switch. Possible returns:
            RebootSendOk(100),          Reboot command was executed without errors, we schedule reboot to 5 seconds
            RebootSendFail(101),        If Reboot sends fails
        
        RebootFailSafe      (2) -       Reboot the switch in failsafe mode.
            RebootFailSafeSendOk(200),  Reboot command was executed without errors, we schedule reboot to 5 seconds
            RebootFailSafeSendFail(201),If command fails.
        
        SaveConf            (3) -       Save actual values in .conf file (Only loadable values)
            SaveConfOk(300),            The configuration was saved without fails.
            SaveConfFail(301),          The configuration file cannot be created.
            SaveConfWarning(302),       The configuration was created but some paremeters could not be saved.
      
        SaveConfApply       (4) -       Save actual values in .conf file (Only loadable values) and try to write the values.
            SaveConfApplyOk(400),       All was ok. All was saved and applied
            SaveConfApplyFail(401),     The configuration file cannot be created.
            SaveConfApplyWarning(402),  The configuration file cannot be created, but some parameter could not be saved or applied
      
        SaveConfReboot      (5) -       Save actual values in .conf file (Only loadable values) and reboot the switch
            SaveConfRebootOk(500),      All was ok.
            SaveConfRebootFail(501),    The configuration file cannot be saved or reboot command fails.
            SaveConfRebootWarning(502)  Some parameters could not be saved in its config file.
            
        Please read wrztParamXConfigVal to understand how to change config values.
        "
        
    ::= { wrzTPFamily 99 }


--
-- NOTIFICATIONS
--

wrzModuleIndexEvent OBJECT-TYPE
    SYNTAX    Unsigned32
    MAX-ACCESS  accessible-for-notify
    STATUS    current
    DESCRIPTION
        "Hearbeat to the modules. Check every 30 seconds."
::= { wrzNotificationsObjects 1 }

wrzPrefixIndexEvent OBJECT-TYPE
    SYNTAX    Unsigned32
    MAX-ACCESS  accessible-for-notify
    STATUS    current
    DESCRIPTION
        "Hearbeat to the modules. Check every 30 seconds."
::= { wrzNotificationsObjects 2 }

wrzParamIndexEvent OBJECT-TYPE
    SYNTAX    Unsigned32
    MAX-ACCESS  accessible-for-notify
    STATUS    current
    DESCRIPTION
        "Hearbeat to the modules. Check every 30 seconds."
::= { wrzNotificationsObjects 3 }

wrzModuleNameEvent OBJECT-TYPE
    SYNTAX    DisplayString
    MAX-ACCESS  accessible-for-notify
    STATUS    current
    DESCRIPTION
        "Hearbeat to the modules. Check every 30 seconds."
::= { wrzNotificationsObjects 4 }

wrzPrefixNameEvent OBJECT-TYPE
    SYNTAX    DisplayString
    MAX-ACCESS  accessible-for-notify
    STATUS    current
    DESCRIPTION
        "Hearbeat to the modules. Check every 30 seconds."
::= { wrzNotificationsObjects 5 }

wrzParamNameEvent OBJECT-TYPE
    SYNTAX    DisplayString
    MAX-ACCESS  accessible-for-notify
    STATUS    current
    DESCRIPTION
        "Hearbeat to the modules. Check every 30 seconds."
::= { wrzNotificationsObjects 6 }

wrzParamValEvent OBJECT-TYPE
    SYNTAX    DisplayString
    MAX-ACCESS  accessible-for-notify
    STATUS    current
    DESCRIPTION
        "Hearbeat to the modules. Check every 30 seconds."
::= { wrzNotificationsObjects 7 }

wrzParamStatusEvent OBJECT-TYPE
    SYNTAX    DisplayString
    MAX-ACCESS  accessible-for-notify
    STATUS    current
    DESCRIPTION
        "Hearbeat to the modules. Check every 30 seconds."
::= { wrzNotificationsObjects 8 }

wrzModuleStatusEvent OBJECT-TYPE
    SYNTAX    DisplayString
    MAX-ACCESS  accessible-for-notify
    STATUS    current
    DESCRIPTION
        "Hearbeat to the modules. Check every 30 seconds."
::= { wrzNotificationsObjects 9 }

wrzModuleUp NOTIFICATION-TYPE
    OBJECTS  { 
                wrzModuleIndexEvent,
                wrzModuleNameEvent,
                wrzModuleStatusEvent
                }
    STATUS    current
    DESCRIPTION
        "Notification sended when modules changes from down to up."
::= { wrzNotificationsPrefix 1 }

wrzModuleDown NOTIFICATION-TYPE
    OBJECTS  { 
                wrzModuleIndexEvent,
                wrzModuleNameEvent,
                wrzModuleStatusEvent
                }   STATUS    current
    DESCRIPTION
        "Notification sended when modules changes from up to down."
::= { wrzNotificationsPrefix 2 }

wrzModuleCritical NOTIFICATION-TYPE
    OBJECTS  { 
                wrzModuleIndexEvent,
                wrzPrefixIndexEvent,
                wrzParamIndexEvent,
                wrzModuleNameEvent,
                wrzPrefixNameEvent,
                wrzParamNameEvent,
                wrzParamValEvent,
                wrzParamStatusEvent,
                wrzModuleStatusEvent
                } 
    STATUS    current
    DESCRIPTION
        "Notification sended when a parameter in the module take a value in critical range."
::= { wrzNotificationsPrefix 3 }

wrzModuleWarning NOTIFICATION-TYPE
    OBJECTS  { 
                wrzModuleIndexEvent,
                wrzPrefixIndexEvent,
                wrzParamIndexEvent,
                wrzModuleNameEvent,
                wrzPrefixNameEvent,
                wrzParamNameEvent,
                wrzParamValEvent,
                wrzParamStatusEvent,
                wrzModuleStatusEvent 
                }
    STATUS    current
    DESCRIPTION
        "Notification sended when a parameter in the module take a value in warning range."
::= { wrzNotificationsPrefix 4 }  

wrzParameterUp NOTIFICATION-TYPE
    OBJECTS  { 
                wrzModuleIndexEvent,
                wrzPrefixIndexEvent,
                wrzParamIndexEvent,
                wrzModuleNameEvent,
                wrzPrefixNameEvent,
                wrzParamNameEvent,
                wrzParamStatusEvent
                }  
    STATUS    current
    DESCRIPTION
        "Notification sended when parameter changes from down to up.
        Parameter is down when is not able to sync.
        Parameter is up when is able to sync."
::= { wrzNotificationsPrefix 5 }

wrzParameterDown NOTIFICATION-TYPE
    OBJECTS  { 
                wrzModuleIndexEvent,
                wrzPrefixIndexEvent,
                wrzParamIndexEvent,
                wrzModuleNameEvent,
                wrzPrefixNameEvent,
                wrzParamNameEvent,
                wrzParamStatusEvent
                }   
    STATUS    current
    DESCRIPTION
        "Notification sended when modules changes from up to down.
        Parameter is down when is not able to sync.
        Parameter is up when is able to sync."

::= { wrzNotificationsPrefix 6 }

wrzParameterCritical NOTIFICATION-TYPE
    OBJECTS  { 
                wrzModuleIndexEvent,
                wrzPrefixIndexEvent,
                wrzParamIndexEvent,
                wrzModuleNameEvent,
                wrzPrefixNameEvent,
                wrzParamNameEvent,
                wrzParamValEvent,
                wrzParamStatusEvent,
                wrzModuleStatusEvent
                } 
    STATUS    current
    DESCRIPTION
        "Notification sended when a parameter take a value in critical range."
::= { wrzNotificationsPrefix 7 }


wrzParameterWarning NOTIFICATION-TYPE
    OBJECTS  { 
                wrzModuleIndexEvent,
                wrzPrefixIndexEvent,
                wrzParamIndexEvent,
                wrzModuleNameEvent,
                wrzPrefixNameEvent,
                wrzParamNameEvent,
                wrzParamValEvent,
                wrzParamStatusEvent,
                wrzModuleStatusEvent 
                }
    STATUS    current
    DESCRIPTION
        "Notification sended when a parameter take a value in warning range."
::= { wrzNotificationsPrefix 8 }  
 
END
